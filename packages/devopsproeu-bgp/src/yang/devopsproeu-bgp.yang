module devopsproeu-bgp {

  namespace "http://devopsproeu.com/devopsproeu-bgp";
  prefix devopsproeu-bgp;

  import ietf-inet-types {
    prefix inet;
  }
  import tailf-common {
    prefix tailf;
  }
  import tailf-ncs {
    prefix ncs;
  }
  import tailf-ned-cisco-ios-xr {
    prefix cisco-ios-xr;
  }

  description
    "Example NSO service for BGP provisioning. Demo for DevOpsPro Europe 2025";

  revision 2025-10-30 {
    description
      "Demo revision.";
  }

  list devopsproeu-bgp {
    description "BGP provisioning";
    uses ncs:service-data;
    ncs:servicepoint devopsproeu-bgp-servicepoint;

    key device;
    leaf device {
      type leafref {
        path "/ncs:devices/ncs:device/ncs:name";
      }
      description "Target device.";
    }

    leaf local-as {
      type uint32;
      description "Local autonomous system (AS) number.";
    }

    list neighbors {
      key "address remote-as";
      description "List of BGP neighbors.";

      leaf address {
        type inet:ipv4-address;
        description "IPv4 address of the BGP neighbor.";
      }

      leaf remote-as {
        type uint32;
        description "Remote autonomous system (AS) number.";
      }

      container address-family {
        leaf in-policy {
          type leafref {
            path "/ncs:devices/ncs:device[ncs:name=current()/../../../device]/ncs:config/cisco-ios-xr:route-policy/cisco-ios-xr:name";
          }
          description
            "Reference to an existing inbound route-policy on the target device.";
        }

        leaf out-policy {
          type leafref {
            path "/ncs:devices/ncs:device[ncs:name=current()/../../../device]/ncs:config/cisco-ios-xr:route-policy/cisco-ios-xr:name";
          }
          description
            "Reference to an existing outbound route-policy on the target device.";
        }
      }
    }
  }
}
